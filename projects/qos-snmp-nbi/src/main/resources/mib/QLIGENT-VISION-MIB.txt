-- *****************************************************************
-- Q'ligent Vision MIB
--
-- March 2014, Roman Novokhatsky
--
-- Copyright (c) 2014 by Tecomgroup.
-- All rights reserved.
-- *****************************************************************

QLIGENT-VISION-MIB DEFINITIONS ::= BEGIN

IMPORTS
    MODULE-IDENTITY, OBJECT-TYPE, enterprises, NOTIFICATION-TYPE,
    Integer32, TimeTicks
        FROM SNMPv2-SMI
    TEXTUAL-CONVENTION, AutonomousType, TruthValue, DateAndTime
        FROM SNMPv2-TC
    MODULE-COMPLIANCE, OBJECT-GROUP, NOTIFICATION-GROUP
        FROM SNMPv2-CONF
    SnmpAdminString
        FROM SNMP-FRAMEWORK-MIB
    ItuPerceivedSeverity
        FROM ITU-ALARM-TC-MIB          -- [RFC3877]
    IANAItuProbableCause
        FROM IANA-ITU-ALARM-TC-MIB;     -- [RFC3877]
                
qligentVisionMIB MODULE-IDENTITY
    LAST-UPDATED "201403250000Z"
    ORGANIZATION "Tecomgroup"
    CONTACT-INFO
            "E-mail: info@tecomgroup.com
             http://tecomgroup.com"

    DESCRIPTION
            "This MIB module represents data provided by Q'ligent 
                        Vision:
                        1. Topology of devices                  
                        2. Alarms
            3. Alarm traps
                        4. Measurement results          

            Copyright (c) 2014 by Tecomgroup. All rights reserved."

    REVISION        "201403250000Z"
    DESCRIPTION
            "Initial version (version 1)"
    ::= { tecomgroup 2 }
        
tecomgroup OBJECT IDENTIFIER ::= { enterprises 40554 }

visionObjects      OBJECT IDENTIFIER ::= { qligentVisionMIB 1 }
visionConformance  OBJECT IDENTIFIER ::= { qligentVisionMIB 2 }

visionEntity OBJECT IDENTIFIER ::= { visionObjects 1 }
visionAlarm  OBJECT IDENTIFIER ::= { visionObjects 2 }
visionResult OBJECT IDENTIFIER ::= { visionObjects 3 }

-- Textual Conventions
ElementIndex ::= TEXTUAL-CONVENTION
    DISPLAY-HINT      "d"
    STATUS            current
    DESCRIPTION
            "An arbitrary value that uniquely identifies the table
                        element.  The value should be a small, positive integer."
    SYNTAX Integer32 (1..2147483647)

PhysicalIndexOrZero ::= TEXTUAL-CONVENTION
    DISPLAY-HINT      "d"
    STATUS            current
    DESCRIPTION
            "This textual convention is an extension of the
            ElementIndex convention, which defines a greater than zero
            value used to identify a physical entity.  This extension
            permits the additional value of zero.  The semantics of the
            value zero are object-specific and must, therefore, be
            defined as part of the description of any object that uses
            this syntax.  Examples of the usage of this extension are
            situations where none or all physical entities need to be
            referenced."
    SYNTAX Integer32 (0..2147483647)

PhysicalClass ::= TEXTUAL-CONVENTION
    STATUS            current
    DESCRIPTION
            "An enumerated value which provides an indication of the
            general hardware type of a particular physical entity.
            There are no restrictions as to the number of
            visionPhysicalEntries of each visionPhysicalClass, which must be
            instantiated by an agent.

            The enumeration 'other' is applicable if the physical entity
            class is known, but does not match any of the supported
            values.

            The enumeration 'unknown' is applicable if the physical
            entity class is unknown to the agent.

            The enumeration 'chassis' is applicable if the physical
            entity class is an overall container for networking
            equipment.  Any class of physical entity, except a stack,
            may be contained within a chassis; and a chassis may only
            be contained within a stack.


            The enumeration 'backplane' is applicable if the physical
            entity class is some sort of device for aggregating and
            forwarding networking traffic, such as a shared backplane in
            a modular ethernet switch.  Note that an agent may model a
            backplane as a single physical entity, which is actually
            implemented as multiple discrete physical components (within
            a chassis or stack).

            The enumeration 'container' is applicable if the physical
            entity class is capable of containing one or more removable
            physical entities, possibly of different types.  For
            example, each (empty or full) slot in a chassis will be
            modeled as a container.  Note that all removable physical
            entities should be modeled within a container entity, such
            as field-replaceable modules, fans, or power supplies.  Note
            that all known containers should be modeled by the agent,
            including empty containers.

            The enumeration 'powerSupply' is applicable if the physical
            entity class is a power-supplying component.

            The enumeration 'fan' is applicable if the physical entity
            class is a fan or other heat-reduction component.

            The enumeration 'sensor' is applicable if the physical
            entity class is some sort of sensor, such as a temperature
            sensor within a router chassis.

            The enumeration 'module' is applicable if the physical
            entity class is some sort of self-contained sub-system.  If
            the enumeration 'module' is removable, then it should be
            modeled within a container entity, otherwise it should be
            modeled directly within another physical entity (e.g., a
            chassis or another module).

            The enumeration 'port' is applicable if the physical entity
            class is some sort of networking port, capable of receiving
            and/or transmitting networking traffic.

            The enumeration 'stack' is applicable if the physical entity
            class is some sort of super-container (possibly virtual),
            intended to group together multiple chassis entities.  A
            stack may be realized by a 'virtual' cable, a real
            interconnect cable, attached to multiple chassis, or may in
            fact be comprised of multiple interconnect cables.  A stack
            should not be modeled within any other physical entities,
            but a stack may be contained within another stack.  Only
            chassis entities should be contained within a stack.


            The enumeration 'cpu' is applicable if the physical entity
            class is some sort of central processing unit."
    SYNTAX      INTEGER  {
       other(1),
       unknown(2),
       chassis(3),
       backplane(4),
       container(5),     -- e.g., chassis slot or daughter-card holder
       powerSupply(6),
       fan(7),
       sensor(8),
       module(9),        -- e.g., plug-in card or daughter-card
       port(10),
       stack(11),        -- e.g., stack of multiple chassis entities
       cpu(12)
    }

--           The Physical Entity Table
visionPhysicalTable OBJECT-TYPE
    SYNTAX      SEQUENCE OF VisionPhysicalEntry
    MAX-ACCESS  not-accessible
    STATUS      current
    DESCRIPTION
            "This table contains one row per physical entity.  There is
            always at least one row for an 'overall' physical entity."
    ::= { visionEntity 1 }

visionPhysicalEntry       OBJECT-TYPE
    SYNTAX      VisionPhysicalEntry
    MAX-ACCESS  not-accessible
    STATUS      current
    DESCRIPTION
            "Information about a particular physical entity.

            Each entry provides objects (visionPhysicalDescr,
            visionPhysicalVendorType, and visionPhysicalClass) to help an NMS
            identify and characterize the entry, and objects
            (visionPhysicalContainedIn and visionPhysicalParentRelPos) to help
            an NMS relate the particular entry to other entries in this
            table."
    INDEX   { visionPhysicalIndex }
    ::= { visionPhysicalTable 1 }

VisionPhysicalEntry ::= SEQUENCE {
      visionPhysicalIndex          ElementIndex,
      visionPhysicalDescr          SnmpAdminString,
      visionPhysicalVendorType     AutonomousType,
      visionPhysicalContainedIn    PhysicalIndexOrZero,
      visionPhysicalClass          PhysicalClass,
      visionPhysicalParentRelPos   Integer32,
      visionPhysicalName           SnmpAdminString,
      visionPhysicalHardwareRev    SnmpAdminString,
      visionPhysicalFirmwareRev    SnmpAdminString,
      visionPhysicalSoftwareRev    SnmpAdminString,
      visionPhysicalSerialNum      SnmpAdminString,
      visionPhysicalMfgName        SnmpAdminString,
      visionPhysicalModelName      SnmpAdminString,
      visionPhysicalAlias          SnmpAdminString,
      visionPhysicalAssetID        SnmpAdminString,
      visionPhysicalIsFRU          TruthValue,
      visionPhysicalMfgDate        DateAndTime,
      visionPhysicalUris           OCTET STRING
}

visionPhysicalIndex    OBJECT-TYPE
    SYNTAX      ElementIndex
    MAX-ACCESS  not-accessible
    STATUS      current
    DESCRIPTION
            "The index for this entry."
    ::= { visionPhysicalEntry 1 }

visionPhysicalDescr OBJECT-TYPE
    SYNTAX      SnmpAdminString
    MAX-ACCESS  read-only
    STATUS      current
    DESCRIPTION
            "A textual description of physical entity.  This object
            should contain a string that identifies the manufacturer's
            name for the physical entity, and should be set to a
            distinct value for each version or model of the physical
            entity."
    ::= { visionPhysicalEntry 2 }

visionPhysicalVendorType OBJECT-TYPE
    SYNTAX      AutonomousType
    MAX-ACCESS  read-only
    STATUS      current
    DESCRIPTION
            "An indication of the vendor-specific hardware type of the
            physical entity.  Note that this is different from the
            definition of MIB-II's sysObjectID.

            An agent should set this object to an enterprise-specific
            registration identifier value indicating the specific
            equipment type in detail.  The associated instance of
            visionPhysicalClass is used to indicate the general type of
            hardware device.

            If no vendor-specific registration identifier exists for
            this physical entity, or the value is unknown by this agent,
            then the value { 0 0 } is returned."
    ::= { visionPhysicalEntry 3 }

visionPhysicalContainedIn OBJECT-TYPE
    SYNTAX      PhysicalIndexOrZero
    MAX-ACCESS  read-only
    STATUS      current
    DESCRIPTION
            "The value of visionPhysicalIndex for the physical entity which
            'contains' this physical entity.  A value of zero indicates
            this physical entity is not contained in any other physical
            entity.  Note that the set of 'containment' relationships
            define a strict hierarchy; that is, recursion is not
            allowed.

            In the event that a physical entity is contained by more
            than one physical entity (e.g., double-wide modules), this
            object should identify the containing entity with the lowest
            value of visionPhysicalIndex."
    ::= { visionPhysicalEntry 4 }

visionPhysicalClass OBJECT-TYPE
    SYNTAX      PhysicalClass
    MAX-ACCESS  read-only
    STATUS      current
    DESCRIPTION
            "An indication of the general hardware type of the physical
            entity.

            An agent should set this object to the standard enumeration
            value that most accurately indicates the general class of
            the physical entity, or the primary class if there is more
            than one entity.

            If no appropriate standard registration identifier exists
            for this physical entity, then the value 'other(1)' is
            returned.  If the value is unknown by this agent, then the
            value 'unknown(2)' is returned."
    ::= { visionPhysicalEntry 5 }

visionPhysicalParentRelPos OBJECT-TYPE
    SYNTAX      Integer32 (-1..2147483647)
    MAX-ACCESS  read-only
    STATUS      current
    DESCRIPTION
            "An indication of the relative position of this 'child'
            component among all its 'sibling' components.  Sibling
            components are defined as visionPhysicalEntries that share the
            same instance values of each of the visionPhysicalContainedIn
            and visionPhysicalClass objects.

            An NMS can use this object to identify the relative ordering
            for all sibling components of a particular parent
            (identified by the visionPhysicalContainedIn instance in each
            sibling entry).

            If possible, this value should match any external labeling
            of the physical component.  For example, for a container
            (e.g., card slot) labeled as 'slot #3',
            visionPhysicalParentRelPos should have the value '3'.  Note
            that the visionPhysicalEntry for the module plugged in slot 3
            should have an visionPhysicalParentRelPos value of '1'.

            If the physical position of this component does not match
            any external numbering or clearly visible ordering, then
            user documentation or other external reference material
            should be used to determine the parent-relative position.
            If this is not possible, then the agent should assign a
            consistent (but possibly arbitrary) ordering to a given set
            of 'sibling' components, perhaps based on internal
            representation of the components.


            If the agent cannot determine the parent-relative position
            for some reason, or if the associated value of
            visionPhysicalContainedIn is '0', then the value '-1' is
            returned.  Otherwise, a non-negative integer is returned,
            indicating the parent-relative position of this physical
            entity.

            Parent-relative ordering normally starts from '1' and
            continues to 'N', where 'N' represents the highest
            positioned child entity.  However, if the physical entities
            (e.g., slots) are labeled from a starting position of zero,
            then the first sibling should be associated with an
            visionPhysicalParentRelPos value of '0'.  Note that this
            ordering may be sparse or dense, depending on agent
            implementation.

            The actual values returned are not globally meaningful, as
            each 'parent' component may use different numbering
            algorithms.  The ordering is only meaningful among siblings
            of the same parent component.

            The agent should retain parent-relative position values
            across reboots, either through algorithmic assignment or use
            of non-volatile storage."
    ::= { visionPhysicalEntry 6 }

visionPhysicalName OBJECT-TYPE
    SYNTAX      SnmpAdminString
    MAX-ACCESS  read-only
    STATUS      current
    DESCRIPTION
            "The textual name of the physical entity.  The value of this
            object should be the name of the component as assigned by
            the local device and should be suitable for use in commands
            entered at the device's `console'.  This might be a text
            name (e.g., `console') or a simple component number (e.g.,
            port or module number, such as `1'), depending on the
            physical component naming syntax of the device.

            If there is no local name, or if this object is otherwise
            not applicable, then this object contains a zero-length
            string.

            Note that the value of visionPhysicalName for two physical
            entities will be the same in the event that the console
            interface does not distinguish between them, e.g., slot-1
            and the card in slot-1."
    ::= { visionPhysicalEntry 7 }


visionPhysicalHardwareRev    OBJECT-TYPE
    SYNTAX      SnmpAdminString
    MAX-ACCESS  read-only
    STATUS      current
    DESCRIPTION
            "The vendor-specific hardware revision string for the
            physical entity.  The preferred value is the hardware
            revision identifier actually printed on the component itself
            (if present).

            Note that if revision information is stored internally in a
            non-printable (e.g., binary) format, then the agent must
            convert such information to a printable format, in an
            implementation-specific manner.

            If no specific hardware revision string is associated with
            the physical component, or if this information is unknown to
            the agent, then this object will contain a zero-length
            string."
    ::= { visionPhysicalEntry 8 }

visionPhysicalFirmwareRev    OBJECT-TYPE
    SYNTAX      SnmpAdminString
    MAX-ACCESS  read-only
    STATUS      current
    DESCRIPTION
            "The vendor-specific firmware revision string for the
            physical entity.

            Note that if revision information is stored internally in a
            non-printable (e.g., binary) format, then the agent must
            convert such information to a printable format, in an
            implementation-specific manner.

            If no specific firmware programs are associated with the
            physical component, or if this information is unknown to the
            agent, then this object will contain a zero-length string."
    ::= { visionPhysicalEntry 9 }

visionPhysicalSoftwareRev    OBJECT-TYPE
    SYNTAX      SnmpAdminString
    MAX-ACCESS  read-only
    STATUS      current
    DESCRIPTION
            "The vendor-specific software revision string for the
            physical entity.

            Note that if revision information is stored internally in a


            non-printable (e.g., binary) format, then the agent must
            convert such information to a printable format, in an
            implementation-specific manner.

            If no specific software programs are associated with the
            physical component, or if this information is unknown to the
            agent, then this object will contain a zero-length string."
    ::= { visionPhysicalEntry 10 }

visionPhysicalSerialNum   OBJECT-TYPE
    SYNTAX      SnmpAdminString (SIZE (0..32))
    MAX-ACCESS  read-write
    STATUS      current
    DESCRIPTION
            "The vendor-specific serial number string for the physical
            entity.  The preferred value is the serial number string
            actually printed on the component itself (if present).

            On the first instantiation of an physical entity, the value
            of visionPhysicalSerialNum associated with that entity is set
            to the correct vendor-assigned serial number, if this
            information is available to the agent.  If a serial number
            is unknown or non-existent, the visionPhysicalSerialNum will be
            set to a zero-length string instead.

            Note that implementations that can correctly identify the
            serial numbers of all installed physical entities do not
            need to provide write access to the visionPhysicalSerialNum
            object.  Agents which cannot provide non-volatile storage
            for the visionPhysicalSerialNum strings are not required to
            implement write access for this object.

            Not every physical component will have a serial number, or
            even need one.  Physical entities for which the associated
            value of the visionPhysicalIsFRU object is equal to 'false(2)'
            (e.g., the repeater ports within a repeater module), do not
            need their own unique serial number.  An agent does not have
            to provide write access for such entities, and may return a
            zero-length string.

            If write access is implemented for an instance of
            visionPhysicalSerialNum, and a value is written into the
            instance, the agent must retain the supplied value in the
            visionPhysicalSerialNum instance (associated with the same
            physical entity) for as long as that entity remains
            instantiated.  This includes instantiations across all
            re-initializations/reboots of the network management system,
            including those resulting in a change of the physical


            entity's visionPhysicalIndex value."
    ::= { visionPhysicalEntry 11 }

visionPhysicalMfgName   OBJECT-TYPE
    SYNTAX      SnmpAdminString
    MAX-ACCESS  read-only
    STATUS      current
    DESCRIPTION
            "The name of the manufacturer of this physical component.
            The preferred value is the manufacturer name string actually
            printed on the component itself (if present).

            Note that comparisons between instances of the
            visionPhysicalModelName, visionPhysicalFirmwareRev,
            visionPhysicalSoftwareRev, and the visionPhysicalSerialNum
            objects, are only meaningful amongst visionPhysicalEntries with
            the same value of visionPhysicalMfgName.

            If the manufacturer name string associated with the physical
            component is unknown to the agent, then this object will
            contain a zero-length string."
    ::= { visionPhysicalEntry 12 }

visionPhysicalModelName   OBJECT-TYPE
    SYNTAX      SnmpAdminString
    MAX-ACCESS  read-only
    STATUS      current
    DESCRIPTION
            "The vendor-specific model name identifier string associated
            with this physical component.  The preferred value is the
            customer-visible part number, which may be printed on the
            component itself.

            If the model name string associated with the physical
            component is unknown to the agent, then this object will
            contain a zero-length string."
    ::= { visionPhysicalEntry 13 }

visionPhysicalAlias    OBJECT-TYPE
    SYNTAX      SnmpAdminString (SIZE (0..32))
    MAX-ACCESS  read-write
    STATUS      current
    DESCRIPTION
            "This object is an 'alias' name for the physical entity, as
            specified by a network manager, and provides a non-volatile
            'handle' for the physical entity.

            On the first instantiation of a physical entity, the value


            of visionPhysicalAlias associated with that entity is set to
            the zero-length string.  However, the agent may set the
            value to a locally unique default value, instead of a
            zero-length string.

            If write access is implemented for an instance of
            visionPhysicalAlias, and a value is written into the instance,
            the agent must retain the supplied value in the
            visionPhysicalAlias instance (associated with the same physical
            entity) for as long as that entity remains instantiated.
            This includes instantiations across all
            re-initializations/reboots of the network management system,
            including those resulting in a change of the physical
            entity's visionPhysicalIndex value."
    ::= { visionPhysicalEntry 14 }

visionPhysicalAssetID OBJECT-TYPE
    SYNTAX      SnmpAdminString (SIZE (0..32))
    MAX-ACCESS  read-write
    STATUS      current
    DESCRIPTION
            "This object is a user-assigned asset tracking identifier
            (as specified by a network manager) for the physical entity,
            and provides non-volatile storage of this information.

            On the first instantiation of a physical entity, the value
            of visionPhysicalAssetID associated with that entity is set to
            the zero-length string.

            Not every physical component will have an asset tracking
            identifier, or even need one.  Physical entities for which
            the associated value of the visionPhysicalIsFRU object is equal
            to 'false(2)' (e.g., the repeater ports within a repeater
            module), do not need their own unique asset tracking
            identifier.  An agent does not have to provide write access
            for such entities, and may instead return a zero-length
            string.

            If write access is implemented for an instance of
            visionPhysicalAssetID, and a value is written into the
            instance, the agent must retain the supplied value in the
            visionPhysicalAssetID instance (associated with the same
            physical entity) for as long as that entity remains
            instantiated.  This includes instantiations across all
            re-initializations/reboots of the network management system,
            including those resulting in a change of the physical
            entity's visionPhysicalIndex value.


            If no asset tracking information is associated with the
            physical component, then this object will contain a
            zero-length string."
    ::= { visionPhysicalEntry 15 }

visionPhysicalIsFRU OBJECT-TYPE
    SYNTAX      TruthValue
    MAX-ACCESS  read-only
    STATUS      current
    DESCRIPTION
            "This object indicates whether or not this physical entity
            is considered a 'field replaceable unit' by the vendor.  If
            this object contains the value 'true(1)' then this
            visionPhysicalEntry identifies a field replaceable unit.  For
            all visionPhysicalEntries that represent components
            permanently contained within a field replaceable unit, the
            value 'false(2)' should be returned for this object."
    ::= { visionPhysicalEntry 16 }

visionPhysicalMfgDate  OBJECT-TYPE
    SYNTAX      DateAndTime
    MAX-ACCESS  read-only
    STATUS      current
    DESCRIPTION
            "This object contains the date of manufacturing of the
            managed entity.  If the manufacturing date is unknown or not
            supported, the object is not instantiated.  The special
            value '0000000000000000'H may also be returned in this
            case."
    ::= { visionPhysicalEntry 17 }

visionPhysicalUris OBJECT-TYPE
    SYNTAX      OCTET STRING
    MAX-ACCESS  read-write
    STATUS      current
    DESCRIPTION
            "This object contains additional identification information
            about the physical entity.  The object contains URIs and,
            therefore, the syntax of this object must conform to RFC
            3986, section 2.

            Multiple URIs may be present and are separated by white
            space characters.  Leading and trailing white space
            characters are ignored.

            If no additional identification information is known
            about the physical entity or supported, the object is not
            instantiated.  A zero length octet string may also be


            returned in this case."
    REFERENCE
            "RFC 3986, Uniform Resource Identifiers (URI): Generic
            Syntax, section 2, August 1998."

    ::= { visionPhysicalEntry 18 }

-- physical mapping table
visionPhysicalContainsTable OBJECT-TYPE
    SYNTAX      SEQUENCE OF VisionPhysicalContainsEntry
    MAX-ACCESS  not-accessible
    STATUS      current
    DESCRIPTION
            "A table that exposes the container/'containee'
            relationships between physical entities.  This table
            provides all the information found by constructing the
            virtual containment tree for a given visionPhysicalTable, but
            in a more direct format.

            In the event a physical entity is contained by more than one
            other physical entity (e.g., double-wide modules), this
            table should include these additional mappings, which cannot
            be represented in the visionPhysicalTable virtual containment
            tree."
    ::= { visionEntity 2 }

visionPhysicalContainsEntry OBJECT-TYPE
    SYNTAX      VisionPhysicalContainsEntry
    MAX-ACCESS  not-accessible
    STATUS      current
    DESCRIPTION
            "A single container/'containee' relationship."
    INDEX       { visionPhysicalIndex, visionPhysicalChildIndex }
    ::= { visionPhysicalContainsTable 1 }

VisionPhysicalContainsEntry ::= SEQUENCE {
      visionPhysicalChildIndex     ElementIndex      
}

visionPhysicalChildIndex OBJECT-TYPE
    SYNTAX      ElementIndex
    MAX-ACCESS  read-only
    STATUS      current
    DESCRIPTION
            "The value of visionPhysicalIndex for the contained physical
            entity."
    ::= { visionPhysicalContainsEntry 1 }

-- Top level entities table
visionPhysicalTopLevelTable OBJECT-TYPE
    SYNTAX      SEQUENCE OF VisionPhysicalTopLevelEntry
    MAX-ACCESS  not-accessible
    STATUS      current
    DESCRIPTION
            "This table contains all physical entities, that don't
            have a parent and thus are top level entities"
    ::= { visionEntity 3 }

visionPhysicalTopLevelEntry OBJECT-TYPE
    SYNTAX      VisionPhysicalTopLevelEntry
    MAX-ACCESS  not-accessible
    STATUS      current
    DESCRIPTION
            "Entries for this tables contain only physical IDs,
            which can be used as an index to query visionPhysicalTable"
    INDEX       { visionTopLevelEntityIndex }
    ::= { visionPhysicalTopLevelTable 1 }

VisionPhysicalTopLevelEntry ::= SEQUENCE {
     visionTopLevelEntityIndex ElementIndex
}

visionTopLevelEntityIndex OBJECT-TYPE
    SYNTAX      ElementIndex
    MAX-ACCESS  read-only
    STATUS      current
    DESCRIPTION
            "Physical index of the entity, which can be used as a key to
            query visionPhysicalTable"
    ::= {visionPhysicalTopLevelEntry 1}

-- Alarm table

VisionAlarmCountNumber ::= TEXTUAL-CONVENTION
    DISPLAY-HINT      "d"
    STATUS            current
    DESCRIPTION
            "Raise count per alarm."
    SYNTAX Integer32 (1..2147483647)
        
VisionAlarmUpdateType ::= TEXTUAL-CONVENTION
    STATUS            current
    DESCRIPTION
            "The type of action occurred with alarm."
    SYNTAX      INTEGER  {
       new(1),
           repeat(2),
           update(3),
           severityUpgrade(4),
           severityDegradation(5),
           autoCleared(6),
           ack(7),
           unack(8),
           operatorCleared(9),
           operatorDeleted(10),
           comment(11),
           agentRestart(12)
    }
        
Float64TC ::= TEXTUAL-CONVENTION
    STATUS       current
    DESCRIPTION  "This type represents a 64-bit (8-octet) IEEE
                  floating-point number in binary interchange format."
    REFERENCE    "IEEE Standard for Floating-Point Arithmetic,
                  Standard 754-2008"
    SYNTAX       OCTET STRING (SIZE(8))

visionAlarmTable OBJECT-TYPE
    SYNTAX      SEQUENCE OF VisionAlarmEntry
    MAX-ACCESS  not-accessible
    STATUS      current
    DESCRIPTION
            "This table contains one row per alarm. Only active alarms
                         are shown."
    ::= { visionAlarm 1 }

visionAlarmEntry       OBJECT-TYPE
    SYNTAX      VisionAlarmEntry
    MAX-ACCESS  not-accessible
    STATUS      current
    DESCRIPTION
            "Information about a particular alarm."
    INDEX   { visionAlarmIndex }
    ::= { visionAlarmTable 1 }

VisionAlarmEntry ::= SEQUENCE {
    visionAlarmIndex                       ElementIndex,
    visionAlarmPerceivedSeverity           ItuPerceivedSeverity,
    visionAlarmProbableCause               IANAItuProbableCause,
    visionAlarmSpecificCause               SnmpAdminString,
    visionAlarmDisplayName                 SnmpAdminString,
    visionAlarmDescription                 SnmpAdminString,
    visionAlarmCreationDateTime            DateAndTime,
    visionAlarmLastUpdateType              VisionAlarmUpdateType,
    visionAlarmLastUpdateDateTime          DateAndTime,       
    visionAlarmAcknowledged                TruthValue,
    visionAlarmAcknowledgeDateTime         DateAndTime,
    visionAlarmDuration                    TimeTicks,
    visionAlarmCount                       VisionAlarmCountNumber,
    visionAlarmThresholdValue              Float64TC,
    visionAlarmDetectionValue              Float64TC,
    visionAlarmSourceId                    ElementIndex,
    visionAlarmParameterId                 ElementIndex,
    visionAlarmOriginatorDisplayName       SnmpAdminString,
    visionAlarmSettings                    SnmpAdminString
}

visionAlarmIndex    OBJECT-TYPE
    SYNTAX      ElementIndex
    MAX-ACCESS  read-only
    STATUS      current
    DESCRIPTION
            "The index for this alarm entry."
    ::= { visionAlarmEntry 1 }

visionAlarmPerceivedSeverity OBJECT-TYPE
    SYNTAX      ItuPerceivedSeverity
    MAX-ACCESS  read-only
    STATUS      current
    DESCRIPTION
            "The perceived severity of alarm according to ITU
                         conventions (RFC3877/ITU-ALARM-TC-MIB)."

    ::= { visionAlarmEntry 2 }
        
visionAlarmProbableCause OBJECT-TYPE
    SYNTAX      IANAItuProbableCause
    MAX-ACCESS  read-only
    STATUS      current
    DESCRIPTION
            "The probable cause of alarm according to ITU-T
                         conventions (RFC3877/IANA-ITU-ALARM-TC-MIB)."

    ::= { visionAlarmEntry 3 }
        
visionAlarmSpecificCause OBJECT-TYPE
    SYNTAX      SnmpAdminString
    MAX-ACCESS  read-only
    STATUS      current
    DESCRIPTION
            "The specific reason of alarm."

    ::= { visionAlarmEntry 4 }
        
visionAlarmDisplayName OBJECT-TYPE
    SYNTAX      SnmpAdminString
    MAX-ACCESS  read-only
    STATUS      current
    DESCRIPTION
            "The human-readable name of alarm."

    ::= { visionAlarmEntry 5 }
        
visionAlarmDescription OBJECT-TYPE
    SYNTAX      SnmpAdminString
    MAX-ACCESS  read-only
    STATUS      current
    DESCRIPTION
            "The string containing additional text information about alarm."

    ::= { visionAlarmEntry 6 }

visionAlarmCreationDateTime OBJECT-TYPE
    SYNTAX      DateAndTime 
    MAX-ACCESS  read-only
    STATUS      current
    DESCRIPTION
            "The date and time when alarm was created."

    ::= { visionAlarmEntry 7 }
        
visionAlarmLastUpdateType OBJECT-TYPE
    SYNTAX      VisionAlarmUpdateType 
    MAX-ACCESS  read-only
    STATUS      current
    DESCRIPTION
            "The type of last update action occurred with alarm.
                        For example: new, severityUpgrade, ack, etc.
                        Please refer the syntax definition for more details."

    ::= { visionAlarmEntry 8 }
        
visionAlarmLastUpdateDateTime OBJECT-TYPE
    SYNTAX      DateAndTime 
    MAX-ACCESS  read-only
    STATUS      current
    DESCRIPTION
            "The last date and time when alarm was updated."

    ::= { visionAlarmEntry 9 }
        
visionAlarmAcknowledged OBJECT-TYPE
    SYNTAX      TruthValue
    MAX-ACCESS  read-only
    STATUS      current
    DESCRIPTION
            "The value of the last action of alarm acknowledgement."

    ::= { visionAlarmEntry 10 }
        
visionAlarmAcknowledgeDateTime OBJECT-TYPE
    SYNTAX      DateAndTime 
    MAX-ACCESS  read-only
    STATUS      current
    DESCRIPTION
            "The date and time of the last acknowledgement of the alarm."

    ::= { visionAlarmEntry 11 }
        
visionAlarmDuration OBJECT-TYPE
    SYNTAX      TimeTicks
    MAX-ACCESS  read-only
    STATUS      current
    DESCRIPTION
            "The duration of alarm activeness."

    ::= { visionAlarmEntry 12 }
        
visionAlarmCount OBJECT-TYPE
    SYNTAX      VisionAlarmCountNumber
    MAX-ACCESS  read-only
    STATUS      current
    DESCRIPTION
            "The value that shows how many times this alarm was changed after 
                         last activation."

    ::= { visionAlarmEntry 13 }
        
visionAlarmThresholdValue OBJECT-TYPE
    SYNTAX      Float64TC
    MAX-ACCESS  read-only
    STATUS      current
    DESCRIPTION
            "The value of threshold condition that caused the alarm activation."

    ::= { visionAlarmEntry 14 }
        
visionAlarmDetectionValue OBJECT-TYPE
    SYNTAX      Float64TC
    MAX-ACCESS  read-only
    STATUS      current
    DESCRIPTION
            "The value of corresponding result parameter at the moment when
                         alarm was activated."

    ::= { visionAlarmEntry 15 }
        
visionAlarmSourceId OBJECT-TYPE
    SYNTAX      ElementIndex
    MAX-ACCESS  read-only
    STATUS      current
    DESCRIPTION
            "The ID of physical entity on which this alarm was raised.
                         The source entity might be found in visionPhysicalTable by this ID.
                         A part of the unique key of the alarm."

    ::= { visionAlarmEntry 16 }

visionAlarmParameterId OBJECT-TYPE
    SYNTAX      ElementIndex
    MAX-ACCESS  read-only
    STATUS      current
    DESCRIPTION
            "ID of the parameter. In case when an alarm is associated with a specific
            parameter, visionAlarmSourceId + visionAlarmParameterId form a composite
            key, which can be used to query visionCurrentResultTable, in order to get
            more information about current status of the parameter. In case when alarm
            is not associated with a specific parameter, this value is 0"

    ::= { visionAlarmEntry 17 }

visionAlarmOriginatorDisplayName OBJECT-TYPE
    SYNTAX      SnmpAdminString
    MAX-ACCESS  read-only
    STATUS      current
    DESCRIPTION
            "Display name of entity that raised the alarm."

    ::= { visionAlarmEntry 18 }
        
visionAlarmSettings OBJECT-TYPE
    SYNTAX      SnmpAdminString
    MAX-ACCESS  read-only
    STATUS      current
    DESCRIPTION
            "The settings of alarm (for example, the name of the parameter).
                         A part of the unique key of the alarm."

    ::= { visionAlarmEntry 19 }

-- Alarm notifications

visionAlarmNotifications  OBJECT IDENTIFIER ::= { visionAlarm 2 }

visionAlarmActiveState NOTIFICATION-TYPE
 OBJECTS     { visionAlarmIndex,
               visionAlarmPerceivedSeverity,
               visionAlarmProbableCause,
               visionAlarmSpecificCause,
               visionAlarmDisplayName,
               visionAlarmDescription,
               visionAlarmCreationDateTime,
               visionAlarmLastUpdateType,
               visionAlarmLastUpdateDateTime,
               visionAlarmAcknowledged,
               visionAlarmAcknowledgeDateTime,
               visionAlarmDuration,
               visionAlarmCount,
               visionAlarmThresholdValue,
               visionAlarmDetectionValue,
               visionAlarmSourceId,
               visionAlarmParameterId,
               visionAlarmOriginatorDisplayName,
               visionAlarmSettings }
 STATUS      current
 DESCRIPTION
    "An instance of the alarm indicated by
    visionAlarmIndex has been raised
    against the entity indicated by
    visionAlarmSourceId."
 ::= { visionAlarmNotifications 1 }

visionAlarmClearState NOTIFICATION-TYPE
   OBJECTS     { visionAlarmIndex,
                 visionAlarmPerceivedSeverity,
                 visionAlarmProbableCause,
                 visionAlarmSpecificCause,
                 visionAlarmDisplayName,
                 visionAlarmDescription,
                 visionAlarmCreationDateTime,
                 visionAlarmLastUpdateType,
                 visionAlarmLastUpdateDateTime,
                 visionAlarmAcknowledged,
                 visionAlarmAcknowledgeDateTime,
                 visionAlarmDuration,
                 visionAlarmCount,
                 visionAlarmThresholdValue,
                 visionAlarmDetectionValue,
                 visionAlarmSourceId,
                 visionAlarmParameterId,
                 visionAlarmOriginatorDisplayName,
                 visionAlarmSettings }
   STATUS      current
   DESCRIPTION
     "An instance of the alarm indicated by
     visionAlarmIndex has been cleared against
     the entity indicated by visionAlarmSourceId."
   ::= { visionAlarmNotifications 2 }

visionAlarmUpdateState NOTIFICATION-TYPE
   OBJECTS     { visionAlarmIndex,
                 visionAlarmPerceivedSeverity,
                 visionAlarmProbableCause,
                 visionAlarmSpecificCause,
                 visionAlarmDisplayName,
                 visionAlarmDescription,
                 visionAlarmCreationDateTime,
                 visionAlarmLastUpdateType,
                 visionAlarmLastUpdateDateTime,
                 visionAlarmAcknowledged,
                 visionAlarmAcknowledgeDateTime,
                 visionAlarmDuration,
                 visionAlarmCount,
                 visionAlarmThresholdValue,
                 visionAlarmDetectionValue,
                 visionAlarmSourceId,
                 visionAlarmParameterId,
                 visionAlarmOriginatorDisplayName,
                 visionAlarmSettings }
   STATUS      current
   DESCRIPTION
     "An instance of the alarm indicated by
     visionAlarmIndex has been updated"
   ::= { visionAlarmNotifications 3 }

-- Current result table
        
VisionResultParameterType ::= TEXTUAL-CONVENTION
    STATUS            current
    DESCRIPTION
            "The range of result parameter type."
    SYNTAX      INTEGER  {
       level(1),
           counter(2),
           percentage(3),
           bool(4),
           property(5)
    }

visionCurrentResultTable OBJECT-TYPE
    SYNTAX      SEQUENCE OF VisionCurrentResultEntry
    MAX-ACCESS  not-accessible
    STATUS      current
    DESCRIPTION
            "This table contains one row per result parameter."
    ::= { visionResult 1 }

visionCurrentResultEntry       OBJECT-TYPE
    SYNTAX      VisionCurrentResultEntry
    MAX-ACCESS  not-accessible
    STATUS      current
    DESCRIPTION
            "Information about a particular result parameter."
    INDEX   { visionCurrentResultTaskId, visionCurrentResultIndex}
    ::= { visionCurrentResultTable 1 }

VisionCurrentResultEntry ::= SEQUENCE {
    visionCurrentResultIndex              ElementIndex,
    visionCurrentResultTaskId             ElementIndex,
    visionCurrentResultType               VisionResultParameterType,
    visionCurrentResultDisplayName        SnmpAdminString,
    visionCurrentResultDescription        SnmpAdminString,
    visionCurrentResultUnits              SnmpAdminString,
    visionCurrentResultValue              Float64TC,
    visionCurrentResultDateTime           DateAndTime
}

visionCurrentResultIndex    OBJECT-TYPE
    SYNTAX      ElementIndex
    MAX-ACCESS  not-accessible
    STATUS      current
    DESCRIPTION
            "Index of result."
    ::= { visionCurrentResultEntry 1 }

visionCurrentResultTaskId    OBJECT-TYPE
    SYNTAX      ElementIndex
    MAX-ACCESS  not-accessible
    STATUS      current
    DESCRIPTION
            "Index of corresponding task in visionPhysicalTable."
    ::= { visionCurrentResultEntry 2 }

visionCurrentResultType    OBJECT-TYPE
    SYNTAX      VisionResultParameterType
    MAX-ACCESS  read-only
    STATUS      current
    DESCRIPTION
            "The type of result parameter."
    ::= { visionCurrentResultEntry 3 }
        
        
visionCurrentResultDisplayName    OBJECT-TYPE
    SYNTAX      SnmpAdminString
    MAX-ACCESS  read-only
    STATUS      current
    DESCRIPTION
            "The human-readable name of result parameter."
    ::= { visionCurrentResultEntry 4 }
        
visionCurrentResultDescription    OBJECT-TYPE
    SYNTAX      SnmpAdminString
    MAX-ACCESS  read-only
    STATUS      current
    DESCRIPTION
            "The string containing additional text information about result parameter."
    ::= { visionCurrentResultEntry 5 }
        
visionCurrentResultUnits    OBJECT-TYPE
    SYNTAX      SnmpAdminString
    MAX-ACCESS  read-only
    STATUS      current
    DESCRIPTION
            "The units of the measurement."
    ::= { visionCurrentResultEntry 6 }
        
visionCurrentResultValue    OBJECT-TYPE
    SYNTAX      Float64TC
    MAX-ACCESS  read-only
    STATUS      current
    DESCRIPTION
            "The last result value."
    ::= { visionCurrentResultEntry 7 }
        
visionCurrentResultDateTime    OBJECT-TYPE
    SYNTAX      DateAndTime
    MAX-ACCESS  read-only
    STATUS      current
    DESCRIPTION
            "The date and time when the last result value was captured."
    ::= { visionCurrentResultEntry 8 }
    
visionCompliances OBJECT IDENTIFIER ::= { visionConformance 1 }
visionGroups      OBJECT IDENTIFIER ::= { visionConformance 2 }

visionCompliance MODULE-COMPLIANCE
    STATUS  current
    DESCRIPTION
            "The compliance statement for SNMP entities that implement
            version 1 of the Q'ligent Vision MIB."
    MODULE  -- this module
        MANDATORY-GROUPS {
            visionMandatoryPhysicalGroup,
            visionMandatoryAlarmGroup,
            visionMandatoryResultGroup
        }
        GROUP visionNotMandatoryPhysicalGroup
        DESCRIPTION
            "Implementation of this group is not mandatory."
            
        GROUP visionNotMandatoryPhysicalContainsGroup
        DESCRIPTION
            "Implementation of this group is not mandatory."
            
        GROUP visionNotMandatoryAlarmGroup
        DESCRIPTION
            "Implementation of this group is not mandatory."
            
        GROUP visionNotMandatoryAlarmNotificationsGroup
        DESCRIPTION
            "Implementation of this group is not mandatory."
            
    ::= { visionCompliances 1 }

-- MIB groupings
visionMandatoryPhysicalGroup    OBJECT-GROUP
    OBJECTS {
      visionPhysicalContainedIn,
      visionPhysicalClass,
      visionPhysicalName
    }
    STATUS  current
    DESCRIPTION
            "The collection of objects used to represent physical
            system components, for which a single agent provides
            management information."
    ::= { visionGroups 1 }
       
visionNotMandatoryPhysicalGroup    OBJECT-GROUP
    OBJECTS {
      visionPhysicalDescr,
      visionPhysicalVendorType,
      visionPhysicalParentRelPos,
      visionPhysicalHardwareRev,
      visionPhysicalFirmwareRev,
      visionPhysicalSoftwareRev,
      visionPhysicalSerialNum,
      visionPhysicalMfgName,
      visionPhysicalModelName,
      visionPhysicalAlias,
      visionPhysicalAssetID,
      visionPhysicalIsFRU,
      visionPhysicalMfgDate,
      visionPhysicalUris
            }
    STATUS  current
    DESCRIPTION
            "The collection of objects used to represent physical
            system components, for which a single agent provides
            management information."
    ::= { visionGroups 2 }
    
visionNotMandatoryPhysicalContainsGroup    OBJECT-GROUP
    OBJECTS {
      visionPhysicalChildIndex
            }
    STATUS  current
    DESCRIPTION
            "The collection of objects used to represent relations
            between physical system components, for which a single
            agent provides management information."
    ::= { visionGroups 3 }

visionMandatoryAlarmGroup    OBJECT-GROUP
    OBJECTS {
      visionAlarmIndex,
      visionAlarmPerceivedSeverity,
      visionAlarmProbableCause,
      visionAlarmDisplayName,
      visionAlarmCreationDateTime,
      visionAlarmLastUpdateType,
      visionAlarmLastUpdateDateTime,       
      visionAlarmAcknowledged,
      visionAlarmDuration,
      visionAlarmCount,
      visionAlarmSourceId,
      visionAlarmOriginatorDisplayName,
      visionAlarmSettings
            }
    STATUS  current
    DESCRIPTION
            "The collection of objects used to represent the list of
            alarms, for which a single agent provides management
            information."
    ::= { visionGroups 4 }
    
visionNotMandatoryAlarmGroup    OBJECT-GROUP
    OBJECTS {
      visionAlarmSpecificCause,
      visionAlarmDescription,
      visionAlarmAcknowledgeDateTime,
      visionAlarmThresholdValue,
      visionAlarmDetectionValue
            }
    STATUS  current
    DESCRIPTION
            "The collection of objects used to represent the list of
            alarms, for which a single agent provides management
            information."
    ::= { visionGroups 5 }
    
visionNotMandatoryAlarmNotificationsGroup    NOTIFICATION-GROUP
    NOTIFICATIONS {
      visionAlarmActiveState,
      visionAlarmClearState,
      visionAlarmUpdateState
                  }
    STATUS  current
    DESCRIPTION
            "The collection of objects used to represent the list of
            alarm notifications."
    ::= { visionGroups 6 }
    
visionMandatoryResultGroup    OBJECT-GROUP
    OBJECTS {
      visionCurrentResultType,
      visionCurrentResultDisplayName,
      visionCurrentResultDescription,
      visionCurrentResultUnits,
      visionCurrentResultValue,
      visionCurrentResultDateTime
            }
    STATUS  current
    DESCRIPTION
            "The collection of objects used to represent the list of
            alarms, for which a single agent provides management
            information."
    ::= { visionGroups 7 }
    
END
